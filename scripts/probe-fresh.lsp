;; probe-fresh.lsp - prints current time + state to a fresh file
(setq fp (open "C:/Users/PCZONE.GE/autocad-mcp/probe-fresh.txt" "w"))
(write-line (strcat "DATE="     (rtos (getvar "CDATE") 2 6)) fp)
(write-line (strcat "DWGNAME="  (getvar "DWGNAME")) fp)
(write-line (strcat "DWGPREFIX=" (getvar "DWGPREFIX")) fp)
(write-line (strcat "CMDNAMES=[" (getvar "CMDNAMES") "]") fp)
(write-line (strcat "CMDACTIVE=" (itoa (getvar "CMDACTIVE"))) fp)
(write-line (strcat "FILEDIA="  (itoa (getvar "FILEDIA"))) fp)
(write-line (strcat "EXPERT="   (itoa (getvar "EXPERT"))) fp)
(setq ss (ssget "_X"))
(write-line (strcat "TOTAL_ENTS=" (if ss (itoa (sslength ss)) "0")) fp)
(close fp)
(princ "\n[probe-fresh] done")
(princ)
